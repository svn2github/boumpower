(defun html-begin-tag(tag f)
  (write-line (strcat "<" tag ">") f)
)
(defun html-end-tag(tag f)
  (write-line (strcat "</" tag ">") f)
)
(defun html-text(text f)
  (write-line text f)
)
(defun html-tag(tag text f)
  (html-begin-tag tag f)
  (if text (html-text text f))
  (html-end-tag tag f)
)


(defun AtomsReport(f); / AtomType Family Atoms tmp1)
  (setq Atoms nil)
  (foreach x (atoms-family 1)
  (setq tmp1 (read (strcat "(type-of " x ")"))) ; list for geting type
  (setq AtomType (if (= (length tmp1) 2)
     (eval tmp1)
     '<SPCL>))

    (setq Family (assoc AtomType Atoms))
    (setq Atoms (if Family 
                   (subst (append Family (list x)) Family Atoms)
                   (cons (list AtomType x) Atoms)))
  )
; Build html file
  (foreach x Atoms
    (setq tmp1 (VL-PRIN1-TO-STRING (car x)))
    (setq tmp1 (substr tmp1 2 (- (strlen tmp1) 2)))
    (html-tag "P" tmp1 f)
  )
  (foreach x Atoms
    (html-begin-tag "TABLE WIDTH=\"100%\" BORDER=\"1\"" f) 
    (setq tmp1 (VL-PRIN1-TO-STRING (car x)))
    (setq tmp1 (substr tmp1 2 (- (strlen tmp1) 2)))
    (html-tag "CAPTION" tmp1 f)
    (foreach y (acad_strlsort (cdr x))
      (html-begin-tag "TR" f)
      (html-tag "TD" y f)
      (cond ((or (= tmp1 "INTEGER") (= tmp1 "FLOAT") (= tmp1 "FUNCTION"))
               (setq tmp2 (eval (read (strcat "(eval " y ")"))))
               (setq tmp2 (VL-PRIN1-TO-STRING tmp2)))
            ((or (= tmp1 "STRING"))
               (setq tmp2 (eval (read y)))
               (setq tmp2 (VL-PRIN1-TO-STRING tmp2)))
            (T (setq tmp2 nil)))
      (html-tag "TD" tmp2 f)
      (html-end-tag "TR" f)
    )
    (html-end-tag "TABLE" f)
  )
)

(defun C:ACADINFO( / f )
  (setq f (open "TestAcadInfo.htm" "w"))
    (html-begin-tag "HTML" f) 
    (html-begin-tag "HEAD" f) 
    (html-tag "TITLE" "AutoCAD Debug Info" f) 
    (html-end-tag "HEAD" f)
    (html-begin-tag "BODY" f) 
    (AtomsReport f)
    (html-end-tag "BODY" f) 
    (html-end-tag "HTML" f) 
  (close f)
  (startapp "IEXPLORE.EXE" (findfile "TestAcadInfo.htm"))
)
