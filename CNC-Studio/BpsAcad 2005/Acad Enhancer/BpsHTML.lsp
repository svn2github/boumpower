;;; génération de fichiers HTML

(vl-load-com)
(vl-doc-export 'html-begin-tag)      
(vl-doc-export 'html-end-tag)      
(vl-doc-export 'html-text)      
(vl-doc-export 'html-tag)      
(vl-doc-export 'html-create)      
(vl-doc-export 'html-done)      
(vl-doc-export 'html-display)      

(defun html-begin-tag(tag f)
  (write-line (strcat "<" tag ">") f)
)
(defun html-end-tag(tag f)
  (write-line (strcat "</" tag ">") f)
)
(defun html-text(text f)
  (write-line text f)
)
(defun html-tag(tag text f)
  (html-begin-tag tag f)
  (if text (html-text text f))
  (html-end-tag tag f)
)

(defun html-create(FName Title / f)
  (setq f (open FName "w"))
    (html-begin-tag "HTML" f) 
    (html-begin-tag "HEAD" f) 
    (html-tag "TITLE" Title f) 
    (html-end-tag "HEAD" f)
    (html-begin-tag "BODY" f)
  f
)

(defun html-done(f)
  (html-end-tag "BODY" f) 
  (html-end-tag "HTML" f) 
  (close f)
)

(defun html-display(FName)
  (startapp "IEXPLORE.EXE" FName)
)
